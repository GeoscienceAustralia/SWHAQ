FME workspace create_HazImp_files_for_mapping_products_using_SA1.fmw

Parameters:
- Scenario_CSV = \\prod.lan\active\ops\community_safety\georisk\HaRIA_B_Wind\projects\qfes_swha\data\derived\scenario_lookup_table.csv   # Scenario lookup CSV
- DestDataset_GEODATABASE_FILE = T:\ops\community_safety\georisk\HaRIA_B_Wind\projects\qfes_swha\data\derived\hazimp\HazImpNEXISV11.gdb   # Destination Esri File Geodatabase
- HazImp_CSV = T:\ops\community_safety\georisk\HaRIA_B_Wind\projects\qfes_swha\data\derived\impact\2020\004-08495\QFES_004-08495.csv   # HazImp CSV File(s)
- SourceDataset_GEODATABASE_FILE = Y:\2_SourceInformation\AdminBoundaries\AdministrativeBoundaries.gdb   # File Geodatabase
- SourceDataset_GEODATABASE_FILE_4 = T:\ops\community_safety\georisk\HaRIA_B_Wind\projects\qfes_swha\maps\MapExtents.gdb   # File Geodatabase

Readers:
- CSV_1: CSV from $(HazImp_CSV) in LL-GDA94
- CSV_2: CSV from $(Scenario_CSV)
- GEODATABASE_FILE_1: GEODATABASE_FILE from $(SourceDataset_GEODATABASE_FILE_4)
- GEODATABASE_FILE_2: GEODATABASE_FILE from $(SourceDataset_GEODATABASE_FILE) in LL-GDA94

Writers:
- GEODATABASE_FILE_3: GEODATABASE_FILE to $(DestDataset_GEODATABASE_FILE)

Note: Filename: create_HazImp_files_for_mapping_products_using_SA1.fmw / Author: Rohan Coghlan (x9836) / Date: 16/10/2018 / Purpose: Calculate HazImp building points statistics per SA1 for given map extent.

Bookmark: Input Data
Note: Map extents of the project
MapExtents (reader GEODATABASE_FILE_1)
    attributes: OBJECTID integer, Region char(50), SHAPE_Length double, SHAPE_Area double
    -> FeatureMerger_3 [REQUESTOR]
Note: SA1 geographical boundaries
SA1_2016_AUST (reader GEODATABASE_FILE_2)
    attributes: OBJECTID integer, SA1_MAIN16 char(11), SA1_7DIG16 char(28), SA2_MAIN16 char(9), SA2_5DIG16 char(20), SA2_NAME16 char(50), SA3_CODE16 char(5), SA3_NAME16 char(50), SA4_CODE16 char(3), SA4_NAME16 char(50), GCC_CODE16 char(5), GCC_NAME16 char(50), STE_CODE16 char(3), STE_NAME16 char(50), AREASQKM16 double, Shape_Length double, Shape_Area double
    -> AttributeKeeper
Note: HAZIMP scenario CSV file
CSV (reader CSV_1)
    attributes: exposure_latitude number(17,13), exposure_longitude number(13,9), LID char(21), MB_CODE number(12,0), MB_CAT char(19), SA1_CODE number(12,0), SA2_CODE number(10,0), SA2_NAME char(27), SA3_CODE number(6,0), SA3_NAME char(18), SA4_CODE number(4,0), SA4_NAME char(9), UCL_CODE number(7,0), UCL_NAME char(35), GCC_CODE char(6), GCC_NAME char(12), LGA_CODE number(6,0), LGA_NAME char(11), SUBURB char(14), POSTCODE number(5,0), YEAR_BUILT char(15), CONSTRUCTION_TYPE char(3), ROOF_TYPE char(33), WALL_TYPE char(33), REPLACEMENT_VALUE number(8,0), CONTENTS_VALUE number(7,0), WIND_VULNERABILTY_MODEL_NUMBER number(4,0), WIND_VULNERABILITY_FUNCTION_ID char(6), AS4055_CLASS char(3), WIND_REGION_CLASSIFCATION char(2),
      WIND_VULNERABILITY_SET char(24), M4 number(17,15), internal_id number(4,0), 0.2s gust at 10m height m/s number(18,15), structural number(31,20), structural_loss number(21,15)
    -> AttributeManager
Note: Scenario_lookup_table. Used to lookup the category and locality for the scenario
CSV (reader CSV_2)
    attributes: ID char(10), Cat number(2,0), Loc char(13)
    -> FeatureMerger_2 [SUPPLIER]

Bookmark: Preprocessing
AttributeKeeper
    CREATE_BULK_MODE_FEATURES = NO
    KEEP_ATTRS = SA1_MAIN16
    -> SpatialFilter [Candidate]
Note: Add the dataset source and current date for QA purposes
AttributeManager
    ATTR_TABLE:
      REMOVE MB_CODE
      RENAME_SET_VALUE SA1_CODE > SA1_MAIN16
      SET_TO ID = @Right(@Value(fme_basename),9)
      SET_TO FME_source = @ReplaceRegEx(@Value(fme_dataset),(\\\\.*\\)(HaR.*),\2)
      SET_TO FME_process_date = @DateTimeFormat(@DateTimeNow(),%Y%m%d%H%M%S )
      RENAME_SET_VALUE structural > structural_loss_ratio
    -> FeatureMerger_2 [REQUESTOR]
Note: Merge with scenario lookup table so category and locality are known
FeatureMerger_2
    ATTR_ACCUM_MODE = Merge Supplier
    ATTR_CONFLICT_RES = Use Requestor
    IGNORE_NULLS = No
    JOIN_KEYS = @Value(ID) @Value(ID) AUTO
    MERGE_TYPE = Attributes Only
    PROCESS_DUPS = No
    REJECT_NULL_MISSING_KEYS = No
    SUPPLIERS_FIRST = No
    MERGED -> AttributeManager_2
    MERGED -> FeatureMerger_3 [SUPPLIER]
Note: Merge with the bld point data to determine which locality extent to use.
FeatureMerger_3
    ATTR_ACCUM_MODE = Merge Supplier
    ATTR_CONFLICT_RES = Use Requestor
    IGNORE_NULLS = No
    JOIN_KEYS = @Value(Region) @Value(Loc) AUTO
    MERGE_TYPE = Attributes Only
    PROCESS_DUPS = No
    REJECT_NULL_MISSING_KEYS = No
    SUPPLIERS_FIRST = No
    MERGED -> SpatialFilter [Filter]
Note: Select mesh blocks that intersect the map extent
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> PointOnAreaOverlayer [AREA]
Note: Calculate the name of the output dataset. This is used in the two writers
Note: HAZIMP scenario CSV file. Contains building point details for the scenario
AttributeManager_2
    ATTR_TABLE = SET_TO Name = @Value(Loc)_Cat_@Value(Cat)_@Value(ID)
    -> VertexCreator_2
Note: Create point geometry for each feature
VertexCreator_2
    MODE_NAME = Add Point
    XVAL = @Value(exposure_longitude)
    YVAL = @Value(exposure_latitude)
    -> CoordinateSystemSetter
Note: Set the coordinate system
CoordinateSystemSetter
    COORDSYS = LL-WGS84
    -> PointOnAreaOverlayer [POINT]
    -> Sorter

Bookmark: Create polygon outputs
Note: Select points that fall within the selected mesh blocks
PointOnAreaOverlayer
    ATTR_ACCUM_MODE = Merge Incoming
    ATTR_CONFLICT_RES = Use Original
    DEAGGREGATE_INPUT = Yes
    OV_ATTR = _overlaps
    POLYS_FIRST = No
    POINT -> StatisticsCalculator
    AREA -> Tester
Note: mesh block passes if it had points within it
Tester
    BOOL_OP = OR
    TEST_CLAUSE = TEST @Value(_overlaps) > 0
    TEST_MODE = TEST
    PASSED -> Aggregator_5
    PASSED -> FeatureMerger_4 [SUPPLIER]
    FAILED -> FeatureMerger_4 [REQUESTOR]
Note: This merges any parts of a multipart mesh block polygon that had previsouly been split out. It ensures the complete mesh block is represented in the final output
FeatureMerger_4
    ATTR_ACCUM_MODE = Merge Supplier
    ATTR_CONFLICT_RES = Use Requestor
    IGNORE_NULLS = No
    JOIN_KEYS = @Value(SA1_MAIN16) @Value(SA1_MAIN16) AUTO
    MERGE_TYPE = Attributes Only
    PROCESS_DUPS = No
    REJECT_NULL_MISSING_KEYS = No
    SUPPLIERS_FIRST = No
    MERGED -> Aggregator_5
Note: aggregate any multipart polygons
Aggregator_5
    ACCUM_ATTRS_NAME = Get Attributes From One Representative Feature
    AGGREGATE_TYPE = Homogeneous Collection (If Possible)
    GROUP_BY = SA1_MAIN16
    MODE = Geometry - Assemble One Level
    ORDERED = No
    SEP = ,
    AGGREGATE -> AttributeRemover
Note: Removes attributes not required
AttributeRemover
    REMOVE_ATTRS = AS4055_CLASS,CONTENTS_VALUE,ID,_overlaps,SHAPE_Area,WALL_TYPE,exposure_longitude,OBJECTID,SA3_NAME,UCL_NAME,GCC_CODE,LID,ROOF_TYPE,CONSTRUCTION_TYPE,GCC_NAME,0.2s gust at 10m height m/s,POSTCODE,WIND_REGION_CLASSIFCATION,structural_loss,YEAR_BUILT,WIND_VULNERABILITY_FUNCTION_ID,fme_basename,Cat,MB_CAT,internal_id,SA2_NAME,SHAPE_Length,SA4_NAME,REPLACEMENT_VALUE,SA3_CODE,SA4_CODE,UCL_CODE,WIND_VULNERABILTY_MODEL_NUMBER,Loc,SA2_CODE,_predicate,SUBURB,structural_loss_ratio,WIND_VULNERABILITY_SET,exposure_latitude
    -> FeatureMerger [REQUESTOR]
Note: Calc mean and count per Mesh Block Code
StatisticsCalculator
    COMPUTE_HISTOGRAM = NO
    COUNT_ATTR = _count
    GROUP_BY = SA1_MAIN16
    MEAN_ATTR = _mean
    PREPEND_ATTR_NAME_CHOICE = For multiple results only
    STATS_ATTRS = structural_loss_ratio
    SUMMARY -> FeatureMerger [SUPPLIER]
Note: Merge stats back onto mesh blocks
FeatureMerger
    ATTR_ACCUM_MODE = Merge Supplier
    ATTR_CONFLICT_RES = Use Requestor
    IGNORE_NULLS = No
    JOIN_KEYS = @Value(SA1_MAIN16) @Value(SA1_MAIN16) AUTO
    MERGE_TYPE = Attributes Only
    PROCESS_DUPS = No
    REJECT_NULL_MISSING_KEYS = No
    SUPPLIERS_FIRST = No
    MERGED -> AttributeManager_4
Note: Update the processed time for QA purposes
AttributeManager_4
    ATTR_TABLE = SET_TO FME_process_date = @DateTimeFormat(@DateTimeNow(),%Y%m%d%H%M%S )
    -> ClassifyDamageState_2
Note: Add a damage state category to each attribute
ClassifyDamageState_2: AttributeRangeMapper
    IN_ATTR = _mean
    LUT = 0,0.005,No damage,0.005,0.02,Negligible,0.02,0.1,Slight,0.1,0.2,Moderate,0.2,0.5,Extensive,0.5,1.0,Complete,,,
    OUT_ATTR = damage_state
    -> CSV0100 (writer GEODATABASE_FILE_3)
Note: Wirte mesh blocks with stats out to GDB
CSV0100 (writer GEODATABASE_FILE_3)
    attributes: SA1_MAIN16 char(20), avg_structural_loss_ratio double, count_hazimp_pts double, FME_source char(100), FME_process_date date, damage_state char(20)

Bookmark: Create sorted bld point output
Note: Sort the points by structural_loss_ratio . This ensures higher structural_loss_ratio values will draw over the top of lower ones when creating map layouts in Esri.
Sorter [off]
    SORT_PARM = structural_loss_ratio NUMERIC ASCENDING
    SORTED -> ClassifyDamageState [off]
Note: Add a damage state category to each attribute
ClassifyDamageState: AttributeRangeMapper [off]
    IN_ATTR = structural_loss
    LUT = 0,0.02,Negligible,0.02,0.1,Slight,0.1,0.2,Moderate,0.2,0.5,Extensive,0.5,1,Complete,,,
    OUT_ATTR = damage_state
    -> a (writer GEODATABASE_FILE_3) [off]
Note: Write the points out to GDB
a (writer GEODATABASE_FILE_3) [off]
    attributes: exposure_latitude double, exposure_longitude double, LID char(20), SA2_NAME char(50), structural_loss_ratio double, SA2_CODE integer, WIND_VULNERABILITY_FUNCTION_ID char(5), WIND_VULNERABILITY_SET char(24), GCC_CODE char(6), POSTCODE integer, WIND_REGION_CLASSIFCATION char(2), LGA_CODE double, LGA_NAME char(50), WALL_TYPE char(33), AS4055_CLASS char(4), ROOF_TYPE char(40), SA4_CODE double, internal_id integer, UCL_NAME char(40), MB_CODE double, MB_CAT char(40), CONSTRUCTION_TYPE char(3), YEAR_BUILT char(15), SA3_CODE double, structural_loss double, SUBURB char(40), UCL_CODE double, REPLACEMENT_VALUE double, CONTENTS_VALUE double, GCC_NAME char(11),
      WIND_VULNERABILTY_MODEL_NUMBER double, _0_2s_gust_at_10m_height_m_s double, SA3_NAME char(40), SA4_NAME char(36), SA1_CODE double, FME_source char(100), FME_process_date date, damage_state char(20)
