FME workspace Convert_tracks_to_points.fmw

Parameters:
- SourceDataset = \\prod.lan\active\ops\community_safety\georisk\HaRIA_B_Wind\projects\qfes_swha\data\derived\tracks\seq\track.004-08495c.line.shp   # Source Shapefile(s)
- OutputPath = \\prod.lan\active\ops\community_safety\georisk\HaRIA_B_Wind\projects\qfes_swha\data\derived\tracks\seq   # Output Directory

Readers:
- ESRISHAPE_1: ESRISHAPE from $(SourceDataset)

Writers:
- ESRISHAPE_2: ESRISHAPE to \\prod.lan\active\ops\community_safety\georisk\HaRIA_B_Wind\projects\qfes_swha\data\derived\tracks

Note: This is a TCRM-format track shape file. First instance, these are created as line feature shape files after they have been extracted from the TCHA database.
track.000-08534.line (reader ESRISHAPE_1)
    attributes: CycloneNumb short, TimeElapsed float, Longitude float, Latitude float, Speed float, Bearing float, pCentre float, pEnv float, rMax float, Year short, Month short, Day short, Hour short, Minute short
    -> VertexCreator
Note: Create points from the vertices in the line features
VertexCreator
    MODE_NAME = Replace with Point
    XVAL = @Value(Longitude)
    YVAL = @Value(Latitude)
    -> AttributeRangeMapper
Note: The 'category' attribute is used to map central pressure values ('pCentre' attribute) to an estimated TC category.
AttributeRangeMapper
    IN_ATTR = pCentre
    LUT = 0,930,5,930,955,4,955,970,3,970,985,2,985,995,1,995,1100,0,,,
    OUT_ATTR = Category
    -> StringSearcher
Note: Extract the track Id from the file name to construct the output file name
StringSearcher
    CASE = no
    MATCHED_PARTS_ATTR = sub_matches
    MATCHED_RESULT_ATTR = trackId
    REGEXP = track.(\d{3}-\d{5}\w*).line.shp
    STRING_TO_SEARCH = @Value(fme_dataset)
    MATCHED -> track.001-08611.point (writer ESRISHAPE_2)
track.001-08611.point (writer ESRISHAPE_2)
    attributes: CycloneNum short, TimeElapse float, Longitude float, Latitude float, Speed float, Bearing float, pCentre float, pEnv float, rMax float, Year short, Month short, Day short, Hour short, Minute short, category short
