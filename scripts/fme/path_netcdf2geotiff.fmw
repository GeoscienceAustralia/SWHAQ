FME workspace path_netcdf2geotiff.fmw

Parameters:
- SourceDataset_NETCDF = T:\ops\community_safety\georisk\HaRIA_B_Wind\projects\qfes_swha\data\derived\hazard\wm_combined\windspeed_2_yr_clip.nc   # Source NetCDF File(s)
- DestDataset_GEOTIFF = T:\ops\community_safety\georisk\HaRIA_B_Wind\projects\qfes_swha\data\derived\hazard\wm_combined   # Destination GeoTIFF Folder

Readers:
- PATH_1: PATH from T:\ops\community_safety\georisk\HaRIA_B_Wind\projects\qfes_swha\data\derived\hazard\wm_combined
- NETCDF_1: NETCDF from $(SourceDataset_NETCDF) in LL-GDA94

Writers:
- GEOTIFF_1: GEOTIFF to $(DestDataset_GEOTIFF)

NETCDF (reader NETCDF_1)
    attributes: NCO char
    -> RasterExpressionEvaluator [A]
RasterExpressionEvaluator
    EXPRESSION_LIST = INTERPRETATION_LIST "AUTO" EXPRESSION_LIST "@if(A[0] <= 0.0, 0.0, A[0])"
    MODE = One Raster
    RESULT -> RasterSingularCellValueCalculator
RasterSingularCellValueCalculator
    OPERAND_ORDER = raster (operation) numeric value
    OPERATION = *
    PRESERVE_INTERPRETATION = Yes
    SCALAR = 3.6
    -> NETCDF (writer GEOTIFF_1)
NETCDF (writer GEOTIFF_1)
    attributes: NCO char(254)
