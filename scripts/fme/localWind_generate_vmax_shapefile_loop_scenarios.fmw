FME workspace localWind_generate_vmax_shapefile_loop_scenarios.fmw

Parameters:
- Scenario_list = \\prod.lan\active\ops\community_safety\georisk\HaRIA_B_Wind\projects\qfes_swha\data\derived\scenario_lookup_table.csv   # Scenario list (CSV)
- BasePath = \\prod.lan\active\ops\community_safety\georisk\HaRIA_B_Wind\projects\qfes_swha\data   # Base path

Readers:
- CSV2_1: CSV2 from $(Scenario_list)

CSV (reader CSV2_1)
    attributes: ID string, Cat string, Loc string
    -> WorkspaceRunner
WorkspaceRunner
    BLOCKING = Yes
    WORKSPACE_FILE = $(FME_MF_DIR)localWind_generate_vmax_shapefile_map_extents.fmw
    WORKSPACE_PARAMETERS = SourceDataset_TIFF,$(BasePath)\derived\windfields\local\@Value(ID)\local_wind.tif,Mainlands_shp,$(BasePath)\reference_data\Mainlands_and_Islands_WGS84.shp,SourceDataset_CSV,$(BasePath)\derived\scenario_lookup_table.csv,DestDataset_ESRISHAPE_4,$(BasePath)\derived\windfields\local\shp,SourceDataset_GEODATABASE_FILE,\\prod.lan\active\ops\community_safety\georisk\HaRIA_B_Wind\projects\qfes_swha\maps\MapExtents.gdb
SplitShapefileRunner: WorkspaceRunner
    BLOCKING = Yes
    WORKSPACE_FILE = $(FME_MF_DIR)Local_Wind_split_shapefile_into_cat_files_for_exposure_report_input.fmw
    WORKSPACE_PARAMETERS = SourceDataset_ESRISHAPE,$(BasePath)\derived\windfields\local\shp\@Value(Loc)_Cat_@Value(Cat)_@Value(ID)_local_wind.shp,Output_Parent,$(BasePath)\derived\windfields\local\shp,SourceDataset_GEODATABASE_FILE,\\prod.lan\active\ops\community_safety\georisk\HaRIA_B_Wind\projects\qfes_swha\maps\MapExtents.gdb
