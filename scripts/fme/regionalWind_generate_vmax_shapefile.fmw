FME workspace regionalWind_generate_vmax_shapefile.fmw

Parameters:
- SourceDataset_NETCDF_3 = T:\ops\community_safety\georisk\HaRIA_B_Wind\projects\qfes_swha\data\derived\windfields\regional\014-01920\windfield\gust.014-01920.nc   # Regional Wind NetCDF File
- SourceDataset_CSV = \\prod.lan\active\ops\community_safety\georisk\HaRIA_B_Wind\projects\qfes_swha\data\derived\scenario_lookup_table.csv   # Scenario lookup table
- DestDataset_ESRISHAPE_4 = T:\ops\community_safety\georisk\HaRIA_B_Wind\projects\qfes_swha\data\derived\windfields\regional\SHP   # Output Shapefile Folder
- Mainlands_shp = \\prod.lan\active\ops\community_safety\georisk\HaRIA_B_Wind\projects\qfes_swha\data\reference_data\Mainlands_and_Islands_WGS84.shp   # Mainlands & Islands Shapefile

Readers:
- ESRISHAPE_1: ESRISHAPE from $(Mainlands_shp)
- CSV_1: CSV from $(SourceDataset_CSV)
- NETCDF_1: NETCDF from $(SourceDataset_NETCDF_3)

Writers:
- ESRISHAPE_2: ESRISHAPE to $(DestDataset_ESRISHAPE_4)

Note: Filename: regionalWind_generate_vmax_shapefile.fmw / Author: Rohan Coghlan (x9836) / Date: 15/10/2018 / Purpose: Convert regional windfield raster to shapefile

Bookmark: Input datasets
Note: Coastline dataset. Data will be clipped to the features in this dataseet / Mainlands_and_Islands_WGS84: Mainlands_and_Islands_WGS84 [ESRISHAPE]
Mainlands_and_Islands_WGS84 (reader ESRISHAPE_1)
    attributes: OBJECTID long, FEATURETYP char(32), STATE char(30), FEATUREREL date, FEATURESOU char(150), ATTRIBUTER date, ATTRIBUTES char(150), PLANIMETRI short, REVISED date, GAID char(50), EDITCODE short, SHAPE_AREA double, SHAPE_LEN double
    -> Clipper [CLIPPER]
Note: Scenario_lookup_table that contains list of all scenarios, the intensity, scenario number, etc.
CSV (reader CSV_1)
    attributes: ID char(10), Cat number(2,0), Loc char(13)
    -> FeatureMerger [SUPPLIER]
Note: Regional wind field in netcdf format
NETCDF (reader NETCDF_1)
    attributes: Actions_downloaddata char, Logging_progressbar char, Logging_datestamp char, LTMSLP_path char, Output_path char, TrackGenerator_seasonseed char, BDECK_pressureunits char, radial_profile char, IBTRACS_numberofheadinglines char, LTMSLP_url char, Timeseries_stationid char, StatInterface_kdestep char, created_by char, track_file_date char, IBTRACS_url char, Logging_newlog char, WindfieldInterface_profiletype char, DataProcess_filterseasons char, Actions_dataprocess char, Hazard_plotspeedunits char, Actions_executeevaluate char, Actions_executehazard char, StatInterface_kdetype char, Logging_verbose char, Hazard_minimumrecords char, Region_gridspace char, BDECK_columns char, Input_landmask char, Timeseries_extract char, IBTRACS_speedunits char,
      Actions_createdatabase char, BDECK_speedunits char, IBTRACS_lengthunits char, WindfieldInterface_thetamax char, Logging_loglevel char, Actions_plothazard char, Source_lengthunits char, WindfieldInterface_domain char, IBTRACS_filename char, DataProcess_inputfile char, Source_numberofheadinglines char, Hazard_calculateci char, IBTRACS_pressureunits char, BDECK_dateformat char, track_file char, Actions_executetrackgenerator char, DataProcess_source char, python_version char, WindfieldInterface_plotoutput char, Region_gridinc char, WindfieldInterface_beta char, created_on char, Hazard_years char, IBTRACS_dateformat char, WindfieldInterface_windfieldtype char, DataProcess_startseason char, BDECK_lengthunits char, Input_mslpfile char, TrackGenerator_trackseed char, Source_speedunits char,
      StatInterface_minsamplescell char, IBTRACS_path char, Actions_executewindfield char, BDECK_fielddelimiter char, IBTRACS_columns char, BDECK_numberofheadinglines char, Input_datasets char, Actions_plotdata char, RMW_getrmwdistfrominputdata char, Source_pressureunits char, StatInterface_kde2dtype char, TrackGenerator_format char, beta double, Timeseries_locationfile char, TrackGenerator_numtimesteps char, Hazard_extremevaluedistribution char, WindfieldInterface_margin char, WindfieldInterface_resolution char, Hazard_percentilerange char, WindfieldInterface_beta1 char, WindfieldInterface_beta2 char, IBTRACS_fielddelimiter char, tcrm_version char, Output_format char, Hazard_samplesize char, boundary_layer char, TrackGenerator_numsimulations char, Input_locationfile char, Actions_executestat char, TrackGenerator_timestep char,
      LTMSLP_filename char, Source_fielddelimiter char, Logging_logfile char
    -> AttributeFilter_2

Bookmark: Processing
Note: Only process vmax data
AttributeFilter_2
    ATTR_NAME = netcdf_subdataset_name
    ATTR_VALUES = <Empty>,<Missing>,<Null>,<Unfiltered>,vmax
    vmax -> RasterExpressionEvaluator [A]
Note: Reclassify raster. Values are currently hardcoded but could be read from a file if desired. m/s to km/h conversion factored in.
RasterExpressionEvaluator
    EXPRESSION_LIST:
      INTERPRETATION_LIST "AUTO" EXPRESSION_LIST "@if(A[0]*3.6 > 90 && A[0]*3.6 <= 125,1,
      @if(A[0]*3.6 > 125 && A[0]*3.6 <= 170,2,
      @if(A[0]*3.6 > 170 && A[0]*3.6 <= 225,3,
      @if(A[0]*3.6 > 225 && A[0]*3.6 <= 280,4,
      @if(A[0]*3.6 > 280,5,0)))))"
    MODE = One Raster
    RESULT -> RasterToPolygonCoercer
Note: Convert classified raster to polygons
RasterToPolygonCoercer
    EXTRACT_NODATA = Yes
    LABEL_ATTRIBUTE = GRIDCODE
    PRESERVE_ATTRIBUTES = Yes
    POLYGONS -> StringSearcher
Note: Extract scenario ID from the dataset path
StringSearcher
    CASE = no
    MATCHED_PARTS_ATTR = sub_matches
    MATCHED_RESULT_ATTR = _first_match
    REGEXP = gust.(.*).nc
    STRING_TO_SEARCH = @Value(fme_dataset)
    MATCHED -> AttributeManager_3
Note: Extract the event ID to a new field from the dataset path
AttributeManager_3
    ATTR_TABLE:
      RENAME_SET_VALUE GRIDCODE > Category
      SET_TO ID = @Right(@Value(sub_matches{0}.part),9)
    -> Clipper [CLIPPEE]
Note: Clip polygons to coastline
Clipper
    ATTR_ACCUM_MODE = Merge Clipper
    ATTR_CONFLICT_RES = Use Clippee
    BOUNDARY_CASES = Treat as Inside
    CLIPPED_ATTR = _clipped
    CLIP_TYPE = Multiple Clippers
    CONNECT_Z_MODE = First Wins
    CREATE_AGGREGATES = Yes
    LINES_AS_SEGMENTS = No
    PRESERVE_CLIPPEE_EXTENTS = No
    INSIDE -> FeatureMerger [REQUESTOR]
Note: Merge with data from the scenario lookup table
FeatureMerger
    ATTR_ACCUM_MODE = Merge Supplier
    ATTR_CONFLICT_RES = Use Requestor
    IGNORE_NULLS = No
    JOIN_KEYS = @Value(ID) @Value(ID) AUTO
    MERGE_TYPE = Attributes Only
    PROCESS_DUPS = No
    REJECT_NULL_MISSING_KEYS = No
    SUPPLIERS_FIRST = No
    MERGED -> AttributeManager_2
Note: Build the output name using the data from the scenario lookup table
AttributeManager_2
    ATTR_TABLE:
      SET_TO Name = @Value(Loc)_Cat_@Value(Cat)_@Value(ID)
      SET_TO FME_source = @ReplaceRegEx(@Value(fme_dataset),(\\\\.*\\)(HaR.*),\2)
      SET_TO FME_date = @DateTimeFormat(@DateTimeNow(),%Y%m%d%H%M%S )
    -> vmax (writer ESRISHAPE_2)

Bookmark: Output
Note: Write out to shapefile
vmax (writer ESRISHAPE_2)
    attributes: Category short, FME_source char(120), FME_date date
