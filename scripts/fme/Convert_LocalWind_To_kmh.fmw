FME workspace Convert_LocalWind_To_kmh.fmw
Title: Convert to kmh

Parameters:
- SourceDataset_GEOTIFF = T:\ops\community_safety\georisk\HaRIA_B_Wind\projects\qfes_swha\data\derived\windfields\local\020-07522\local_wind.tif   # Source GeoTIFF File(s)
- SourceDataset_ESRISHAPE = T:\ops\community_safety\georisk\HaRIA_B_Wind\projects\qfes_swha\data\reference_data\Mainlands_and_Islands_WGS84.shp   # Source Esri Shapefile(s)
- Scenario = 020-07522   # Scenario ID number
- DestDataset_GEOTIFF_4 = T:\ops\community_safety\georisk\HaRIA_B_Wind\projects\qfes_swha\data\derived\windfields\local\020-07522   # Destination GeoTIFF Folder

Readers:
- GEOTIFF_1: GEOTIFF from $(SourceDataset_GEOTIFF)
- ESRISHAPE_1: ESRISHAPE from $(SourceDataset_ESRISHAPE)

Writers:
- GEOTIFF_2: GEOTIFF to $(DestDataset_GEOTIFF_4)

Note: Coastline boundary file. Data will be clipped to the features contained in this shape file: Mainlands_and_Islands_WGS84 [ESRISHAPE]
Mainlands_and_Islands_WGS84 (reader ESRISHAPE_1)
    attributes: OBJECTID long, FEATURETYP char(32), STATE char(30), FEATUREREL date, FEATURESOU char(150), ATTRIBUTER date, ATTRIBUTES char(150), PLANIMETRI short, REVISED date, GAID char(50), EDITCODE long, SHAPE_AREA double, SHAPE_LEN double
    -> Clipper [CLIPPER]
Note: Input GEOTIFF raster containing local wind speed values: local_wind [GEOTIFF]
GEOTIFF (reader GEOTIFF_1)
    -> Clipper [CLIPPEE]
Clipper
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> ConvertTokmh
Note: Convert values to kilometres per hour
ConvertTokmh: RasterSingularCellValueCalculator
    OPERAND_ORDER = raster (operation) numeric value
    OPERATION = *
    PRESERVE_INTERPRETATION = Yes
    SCALAR = 3.6
    -> RasterMosaicker
RasterMosaicker
    ACCUM_ATTRS_NAME = Use Attributes From One Feature
    INTERPOLATION_TYPE_NAME = Nearest Neighbor
    MERGE_PALETTES_NAME = Yes
    OVERLAPPING_VALUES = max
    SNAPPING_TYPE_NAME = Resample
    -> GEOTIFF (writer GEOTIFF_2)
GEOTIFF (writer GEOTIFF_2)
