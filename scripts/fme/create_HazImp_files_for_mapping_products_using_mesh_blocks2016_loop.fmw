FME workspace create_HazImp_files_for_mapping_products_using_mesh_blocks2016_loop.fmw

Parameters:
- SourceDataset_CSV2 = X:\georisk\HaRIA_B_Wind\projects\qfes_swha\data\derived\scenario_lookup_table.csv   # Source CSV (Comma Separated Value) File(s)
- BasePath = T:\ops\community_safety\georisk\HaRIA_B_Wind\projects\qfes_swha\data\derived\impact\2020   # Base path for impact files

Readers:
- CSV2_1: CSV2 from $(SourceDataset_CSV2)

CSV (reader CSV2_1)
    attributes: ID string, Cat string, Loc string
    -> WorkspaceRunner
WorkspaceRunner
    BLOCKING = Yes
    WORKSPACE_FILE = \\prod.lan\active\ops\community_safety\georisk\HaRIA_B_Wind\projects\qfes_swha\software\fme\create_HazImp_files_for_mapping_products_using_mesh_blocks2016.fmw
    WORKSPACE_PARAMETERS = HAZIMP_CSV,$(BasePath)\@Value(ID)\QFES_@Value(ID).csv,MB_GDB,\\prod.lan\active\ops\built_env\2_SourceInformation\AdminBoundaries\AdministrativeBoundaries.gdb,Scenario_CSV,\\prod.lan\active\ops\community_safety\georisk\HaRIA_B_Wind\projects\qfes_swha\data\derived\scenario_lookup_table.csv,DestDataset_GEODATABASE_FILE,X:\georisk\HaRIA_B_Wind\projects\qfes_swha\data\derived\hazimp\HazImp2020.gdb,SourceDataset_GEODATABASE_FILE_3,X:\georisk\HaRIA_B_Wind\projects\qfes_swha\maps\MapExtents.gdb
